-- Revision 1.83 Draft ---------------------------
-- 2004/1/12 11:50上午  ---------------------------
-- Add a object 'agentBscSwFileBIncrement' in agentBscSwFileTable
-- Add group 'agentCPUutilization'
-- Add swMultiImageCtrlTable ,swMultiImageInfoTable
-- Revision 1.82 Draft ---------------------------
--2003/5/14 02:11下午  ---------------------------
-- re-arrange the agentNotify subtree
-- ------------------------------------------------------------------------ 
-- Revision 1.81 Draft ---------------------------
-- 2003/3/24 03:09下午
-- remove  status "changed-not-save(4)"  in object agentStatusSaveCfg
-- change object  MAX-ACCESS of agentTrapManagerIpAddr  from read-only to read-write 
-- ------------------------------------------------------------------------ 
-- Revision 1.8 Draft ---------------------------
-- 2003/1/21 11:21上午
-- Modified  Common traps and management
-- ----------------------------------------------
-- Remove agentConsoleModeManager , agentSlipModeManager
-- Add Common traps management
-- Revision 1.7
-- Copyright 2000 D-Link Inc.
-- All rights reserved.

DLINK-AGENT-MIB  DEFINITIONS ::= BEGIN

    IMPORTS
        IpAddress			        FROM RFC1155-SMI
        MODULE-IDENTITY, OBJECT-TYPE,
        Integer32		 	FROM SNMPv2-SMI
        TruthValue          FROM SNMPv2-TC
        DisplayString		FROM RFC1213-MIB      
        AgentNotifyLevel    FROM DLINK-ID-REC-MIB      
        dlink-common-mgmt	FROM DLINK-ID-REC-MIB;        
    	
      agentGeneralMgmt MODULE-IDENTITY
	    LAST-UPDATED "0007150000Z"
	    ORGANIZATION "D-Link, Inc."
	    CONTACT-INFO
	        "   D-Link Customer Service

		    Postal: No. 20,Park Ave, II, Science-based
			        Industrial Park, Hsinchu, taiwan, R.O.C.

		       Tel: 886-3-577-9966

		    E-mail: "
	    DESCRIPTION
		    "The Structure of Common Management Information for the
		    D-Link enterprise."
        ::= {  dlink-common-mgmt 1 }

    -- ****************
    -- agentBasicInfo *
    -- ****************
    agentBasicInfo          OBJECT IDENTIFIER ::= { agentGeneralMgmt 1 }
        
    agentMgmtProtocolCapability OBJECT-TYPE
        SYNTAX  INTEGER {   
                    other(1),
                    snmp-ip(2),
                    snmp-ipx(3),
                    snmp-ip-ipx(4)
                }
        MAX-ACCESS  read-only
        STATUS  current
        DESCRIPTION
            "The network management protocol(s) supported by this agent."
        ::= { agentBasicInfo 1 }


    -- *************************
    -- agentMibcapabilityTable *
    -- *************************

    agentMibCapabilityTable OBJECT-TYPE
        SYNTAX  SEQUENCE OF AgentMibCapabilityEntry
        MAX-ACCESS  not-accessible
        STATUS  current
        DESCRIPTION
            "A list of MIB capability entries supported by this agent."    
        ::= { agentBasicInfo 2 }

    agentMibCapabilityEntry OBJECT-TYPE
        SYNTAX  AgentMibCapabilityEntry
        MAX-ACCESS  not-accessible
        STATUS  current
        DESCRIPTION
            "A MIB capability entry contains objects describing a particular MIB
             supported by this agent."
        INDEX   { agentMibCapabilityIndex }
        ::= { agentMibCapabilityTable 1 }

    AgentMibCapabilityEntry ::= 
        SEQUENCE {
            agentMibCapabilityIndex
                Integer32,
            agentMibCapabilityDescr
                DisplayString,
            agentMibCapabilityVersion
                Integer32,
            agentMibCapabilityType
                INTEGER
        }

    agentMibCapabilityIndex OBJECT-TYPE
        SYNTAX  Integer32
        MAX-ACCESS  read-only
        STATUS  current
        DESCRIPTION
            "A list of agentMibCapabilityDescr entries."
        ::= { agentMibCapabilityEntry 1 }

    agentMibCapabilityDescr OBJECT-TYPE
        SYNTAX  DisplayString (SIZE (0..35))
        MAX-ACCESS  read-only
        STATUS  current
        DESCRIPTION
            "The name of the MIB supported by the agent."
        ::= { agentMibCapabilityEntry 2 }

    agentMibCapabilityVersion OBJECT-TYPE
        SYNTAX  Integer32
        MAX-ACCESS  read-only
        STATUS  current
        DESCRIPTION
            "The version of the MIB specified in this entry."
        ::= { agentMibCapabilityEntry 3 }

    agentMibCapabilityType OBJECT-TYPE
        SYNTAX  INTEGER {
                    other(1),
                    standard(2),
                    proprietary(3),
                    experiment(4)
                }
        MAX-ACCESS  read-only
        STATUS  current
        DESCRIPTION
            "The type of the MIB specified in this entry."
        ::= { agentMibCapabilityEntry 4 }


    agentStatusConsoleInUse   OBJECT-TYPE
        SYNTAX INTEGER {
               other(1),
               in-use(2),
               not-in-use(3)
               }
        MAX-ACCESS read-only
        STATUS current
        DESCRIPTION
            "This indicates whether console is currently in-use."
        ::= { agentBasicInfo 3 }

    agentStatusSaveCfg OBJECT-TYPE
        SYNTAX INTEGER {
               other(1),
               proceeding(2),
               completed(3),
               failed(4)
               }
        MAX-ACCESS read-only
        STATUS current
        DESCRIPTION
            "This indicates the status of the device configuration.
            
            other(1) - this entry is currently in use but the conditions 
                     under which it will remain so are different from each 
                     of the following values.
            proceeding(2) - the device configuration is being currently saved into the NV-RAM.
            completed(3) – all of the device configuration parameters have been
                     saved into NV-RAM.
            failed(4) - The process to save device configuration is failed."
        ::= { agentBasicInfo 4 }

    agentStatusFileTransfer OBJECT-TYPE
        SYNTAX  INTEGER {
                    other(1) ,
                    in-process(2),
                    invalid-file(3),
                    violation(4),
                    file-not-found(5),
                    disk-full(6),
                    complete(7),
                    time-out(8),
                    not-format(9),
                    memory-full(10)
                }
        MAX-ACCESS  read-only
        STATUS  current
        DESCRIPTION
            "status of firmware download control. If the value is 'other',
            means never firmware updated since device started up." 
        ::= { agentBasicInfo 5 } 
 
    -- *************************
    -- agentCPUutilizationTable *
    -- *************************
    agentCPUutilization          OBJECT IDENTIFIER ::= { agentBasicInfo 6 }
    

    agentCPUutilizationIn5sec OBJECT-TYPE
        SYNTAX  Integer32
        MAX-ACCESS  read-only
        STATUS  current
        DESCRIPTION
            "Time scale is 5 seconds.The value will be between 0%(idle) and 100%
            (very busy)."
        ::= { agentCPUutilization 1 }

    agentCPUutilizationIn1min OBJECT-TYPE
        SYNTAX  Integer32

        MAX-ACCESS  read-only
        STATUS  current
        DESCRIPTION
            "Time scale is 1 minute.The value will be between 0%(idle) and 100%
            (very busy)."
        ::= { agentCPUutilization 2 }

    agentCPUutilizationIn5min OBJECT-TYPE
        SYNTAX  Integer32
        MAX-ACCESS  read-only
        STATUS  current
        DESCRIPTION
            "Time scale is 5 minute.The value will be between 0%(idle) and 100%
            (very busy)."
        ::= { agentCPUutilization 3 }
 
    -- ******************
    -- agentBasicConfig *
    -- ******************
    agentBasicConfig        OBJECT IDENTIFIER ::= { agentGeneralMgmt 2 }   

    agentBscSwFileTable OBJECT-TYPE
        SYNTAX  SEQUENCE OF AgentBscSwFileEntry
        MAX-ACCESS  not-accessible
        STATUS  current
        DESCRIPTION
            "A list of MIB Basic Config entries supported file Update by this agent."    
        ::= { agentBasicConfig 1 }    
        
    agentBscSwFileEntry OBJECT-TYPE
        SYNTAX  AgentBscSwFileEntry
        MAX-ACCESS  not-accessible
        STATUS  current
        DESCRIPTION
            "A basic config entry contains objects describing a particular MIB
             supported by this agent."
        INDEX   { agentBscSwFileIndex }
        ::= { agentBscSwFileTable 1 }        

    AgentBscSwFileEntry ::=
    	SEQUENCE {
    		agentBscSwFileIndex
    			Integer32,
    		agentBscSwFileDscr
    			DisplayString,
    		agentBscSwFileAddr
    			IpAddress,
    		agentBscSwFileTransferType
    			INTEGER,
        	agentBscSwFile
        		DisplayString,
        	agentBscSwFileLocateId
        		INTEGER,
        	agentBscSwFileLoadType
        		INTEGER,
        	agentBscSwFileCtrl
        		INTEGER,
        	agentBscSwFileBIncrement
        	    TruthValue,
        	agentMultiImageCtrlID
        		INTEGER

        }

    agentBscSwFileIndex OBJECT-TYPE
    	SYNTAX	Integer32
    	MAX-ACCESS	read-only
    	STATUS	current
    	DESCRIPTION
    		"The table index for the file entry"
    	::= { agentBscSwFileEntry 1 }

    agentBscSwFileDscr OBJECT-TYPE
        SYNTAX  DisplayString  (SIZE (0..64))
        MAX-ACCESS  read-write
        STATUS  current
        DESCRIPTION
            "The description for the purpose of the software file in this entry.
			 Note:
			 For system which does not support change of this object, setting value to 
			 this object will cause the system to return bad-value error message.
			 "
        ::= { agentBscSwFileEntry 2 }
        
    agentBscSwFileAddr OBJECT-TYPE
        SYNTAX  IpAddress
        MAX-ACCESS  read-write
        STATUS  current
        DESCRIPTION
            "The IP address where the File to be downloaded is located, or the IP address
            where the file will be uploaded to."
        ::= {  agentBscSwFileEntry 3 }
            	
    agentBscSwFileTransferType OBJECT-TYPE
        SYNTAX  INTEGER {
                    other(1),
                    network-load(2),
                    out-of-band-load(3)
                }
        MAX-ACCESS  read-write
        STATUS  current
        DESCRIPTION
            "The channel through which the file will be downloaded or uploaded. 

			 Note:
			 For system which does not support all channels, setting value to the unsupported 
			 channel will cause the system to return bad-value error message.
			 "
        ::= { agentBscSwFileEntry 4 }

    agentBscSwFile OBJECT-TYPE
        SYNTAX  DisplayString  (SIZE (0..64))
        MAX-ACCESS  read-write
        STATUS  current
        DESCRIPTION
            "The name of the file to be downloaded from the TFTP server, or to be uploaded
            to."
        ::= { agentBscSwFileEntry 5 }
        
     agentBscSwFileLocateId OBJECT-TYPE
        SYNTAX  INTEGER (1..16)
        MAX-ACCESS  read-write
        STATUS  current
        DESCRIPTION
            "This object describes the type of the file.
             runtime-code(1),
             log-file(2),
             cfg-file(3)
             
			 Note:
			 For system which does not support change of this object, setting value to 
			 this object will cause the system to return bad-value error message.
             " 
        ::= { agentBscSwFileEntry 6 }
        
     agentBscSwFileLoadType OBJECT-TYPE
        SYNTAX  INTEGER {
                    other(1),
                    upload(2),
                    download(3)
                }
        MAX-ACCESS  read-write
        STATUS  current
        DESCRIPTION
        	"This object provides the user to select download or upload function for the file.

			 Note:
			 For system which does not support change of this object, setting value to 
			 this object will cause the system to return bad-value error message.
			 "
        ::= { agentBscSwFileEntry 7 }
                                               
     agentBscSwFileCtrl OBJECT-TYPE
        SYNTAX  INTEGER {
                    other(1),
                    inactive(2),
                    start(3),
                    delete(4),
                    config-as-bootup-fw(5)
                }
        MAX-ACCESS  read-write
        STATUS  current
        DESCRIPTION
            "This object provides the user to download runtime software. The setting 
 		  	 will take effect when the system is restart. See Note(1) below
 		  
			 Note:
			 For system which does not support change of this object to some value, 
			 setting object to these values cause the system to return 
			 bad-value error message
			
			start - start to action.
	        delete(4) - delete the firmware by indicated firmware ID.
	        config-as-bootup-fw(5) - configured as bootup firmware by indicated 
            firmware(ID)."
        ::= { agentBscSwFileEntry 8 }

	agentBscSwFileBIncrement OBJECT-TYPE
        SYNTAX     TruthValue
        MAX-ACCESS read-write
        STATUS current
        DESCRIPTION
            "The object indicate that whether the previously configuration will keep valid
              or not after config file downloaded .
             True : keep valid
             False : erase. "
        ::= { agentBscSwFileEntry 9 }       

    agentMultiImageCtrlID OBJECT-TYPE
        SYNTAX  INTEGER
        MAX-ACCESS  read-write
        STATUS  current
        DESCRIPTION
            "The section ID of firmware image."
        ::= { agentBscSwFileEntry 10 }

	agentFileTransfer OBJECT-TYPE
		SYNTAX INTEGER {
				other(1),
				start(2),
				start-and-reset(3),
				noaction(4)
			}
		MAX-ACCESS read-write
		STATUS obsolete
		DESCRIPTION
			"This object will execute the download or upload action. If start(2), it will
			begin to download/upload, but no reset as follow. If start-and-reset(3), then
			the reset will active after download or upload. No action if(4). 

			 Note:
			 Because these functions will be limited by the system support. Some of the 
			 select item will invalid. When one of the item user select,it will response with 
			 bad-value status."
		::= { agentBasicConfig 2 }
				
    agentSystemReset OBJECT-TYPE
        SYNTAX  INTEGER {
                    other(1),
                    cold-start(2),
                    warm-start(3),
                    no-reset(4)
                }
        MAX-ACCESS  read-write
        STATUS  current
        DESCRIPTION
            "This object indicates the agent system reset state. Setting this
             object to no-reset(4) has no effect. Setting this object to
             cold-start(2) or warm-start(3) will reset the agent. The agent 
             always returns no-reset(4) when this object is read."
        ::= { agentBasicConfig 3 }

    agentRs232PortConfig OBJECT-TYPE
        SYNTAX  INTEGER  {
                    other(1),
                    console(2),
                    out-of-band(3),
					notAvail(4)
                }
        MAX-ACCESS  read-write
        STATUS  current
        DESCRIPTION
            "This object indicates the RS-232C mode while device restart."
        ::= { agentBasicConfig 4 }

    agentOutOfBandBaudRateConfig OBJECT-TYPE
        SYNTAX  INTEGER {
                    other(1),
                    baudRate-2400 (2),
                    baudRate-9600 (3),
                    baudRate-19200(4),
                    baudRate-38400(5),
                    baudRate-115200(6)
                }
        MAX-ACCESS  read-write
        STATUS  obsolete
        DESCRIPTION
            "This object allows user to specify out_of_band baud rate. It will take effect
			 when the system is restart. 
			 
			 Note:
			 Because these funiction will be limited by the system support. Some of the 
			 select item will invalid. When one of the item user select,it will response with 
			 bad-value status.			 
			 "
        ::= { agentBasicConfig 5 }

     agentSaveCfg OBJECT-TYPE
        SYNTAX INTEGER {
        			other(1),
        			idle(2),
        			set(3)
        		}
        MAX-ACCESS read-write
        STATUS current
        DESCRIPTION
            "As the object is set to 'set(3)', the current device configuration will be saved
             into to NV-RAM."
        ::= { agentBasicConfig 6 }                

--***************************************************************************
--swMultiImageInfoTable
--***************************************************************************
    swMultiImageInfoTable OBJECT-TYPE
        SYNTAX  SEQUENCE OF SwMultiImageInfoEntry
        MAX-ACCESS  not-accessible
        STATUS  current
        DESCRIPTION
            ""
        ::= { agentBasicConfig 7 }
        
    swMultiImageInfoEntry OBJECT-TYPE
        SYNTAX  SwMultiImageInfoEntry
        MAX-ACCESS  not-accessible
        STATUS  current
        DESCRIPTION
            "A list of information about multiple image management."
        INDEX  { swMultiImageInfoID }
        ::= { swMultiImageInfoTable 1 }
      
    SwMultiImageInfoEntry ::= 
        SEQUENCE {
        	swMultiImageInfoID
        		INTEGER,
            swMultiImageVersion
                DisplayString,
            swMultiImageSize
                Integer32,
            swMultiImageUpdateTime
                DisplayString,
            swMultiImageFrom
                DisplayString,               
            swMultiImageSendUser
                DisplayString                                                 
        }
    swMultiImageInfoID OBJECT-TYPE
        SYNTAX  INTEGER
        MAX-ACCESS  read-only
        STATUS  current
        DESCRIPTION
            "The section ID of firmware image."
        ::= { swMultiImageInfoEntry 1 }
             
    swMultiImageVersion OBJECT-TYPE
        SYNTAX  DisplayString  (SIZE (0..32))
        MAX-ACCESS  read-only
        STATUS  current
        DESCRIPTION
            "The record of downloaded firmware version."
        ::= { swMultiImageInfoEntry 2 }
        
    swMultiImageSize OBJECT-TYPE
        SYNTAX  Integer32
        MAX-ACCESS  read-only
        STATUS  current
        DESCRIPTION
            "The record of downloaded firmware size."
        ::= { swMultiImageInfoEntry 3 }

    swMultiImageUpdateTime OBJECT-TYPE
        SYNTAX  DisplayString  (SIZE (0..32))
        MAX-ACCESS  read-only
        STATUS  current
        DESCRIPTION
            "The record of firmware updated time."
        ::= { swMultiImageInfoEntry 4 }

    swMultiImageFrom OBJECT-TYPE
        SYNTAX  DisplayString  (SIZE (0..32))
        MAX-ACCESS  read-only
        STATUS  current
        DESCRIPTION
            "The record of ip address of tftp server."
        ::= { swMultiImageInfoEntry 5 }

    swMultiImageSendUser OBJECT-TYPE
        SYNTAX  DisplayString  (SIZE (0..32))
        MAX-ACCESS  read-only
        STATUS  current
        DESCRIPTION
            "The record of user who download the firmware."
        ::= { swMultiImageInfoEntry 6 }

--***************************************************************************
--swMultiImageCtrlTable
--***************************************************************************
--    swMultiImageCtrlTable OBJECT-TYPE
--        SYNTAX  SEQUENCE OF SwMultiImageCtrlEntry
--        MAX-ACCESS  not-accessible
--        STATUS  current
--        DESCRIPTION
--            ""
--        ::= { agentBasicConfig 8 }
        
--    swMultiImageCtrlEntry OBJECT-TYPE
--        SYNTAX  SwMultiImageCtrlEntry
--        MAX-ACCESS  not-accessible
--        STATUS  current
--        DESCRIPTION
--            "A list of information about multiple image management."
--        INDEX  { swMultiImageID }
--        ::= { swMultiImageCtrlTable 1 }
      
--    SwMultiImageCtrlEntry ::= 
--        SEQUENCE {
--        	swMultiImageCtrlID
--        		INTEGER,
--            swMultiImageSourceAddr
--                IpAddress,
--            swMultiImageFileName
--                DisplayString,        
--            swMultiImageAction
--                INTEGER                                                        
--        }
--    swMultiImageCtrlID OBJECT-TYPE
--        SYNTAX  INTEGER
--        MAX-ACCESS  read-write
--        STATUS  current
--        DESCRIPTION
--            "The section ID of firmware image."
--        ::= { swMultiImageCtrlEntry 1 }
        
--    swMultiImageSourceAddr OBJECT-TYPE
--        SYNTAX  IpAddress
--        MAX-ACCESS  read-write
--        STATUS  current
--        DESCRIPTION
--            "The ip address where new firmware image file is located on."
--        ::= { swMultiImageCtrlEntry 2 }
        
--    swMultiImageFileName OBJECT-TYPE
--        SYNTAX  DisplayString  (SIZE (0..64))
--        MAX-ACCESS  read-write
--        STATUS  current
--        DESCRIPTION
--            "The full name of the firmware image file to be downloaded."
--        ::= { swMultiImageCtrlEntry 3 }
        
--    swMultiImageAction OBJECT-TYPE
--		SYNTAX  INTEGER {
--               other(1),
--               update(2),
--               delete(3),
--               config-as-bootup-fw(4)
--               }
--        MAX-ACCESS  read-write
--        STATUS  current
--        DESCRIPTION
--            "This object indicates the status of multiImageTable actions. 

--            other(1) - .
--            update(2) - download firmware to indicated section.
--            delete(3) - delete the firmware by indicated firmware ID.
--            config-as-bootup-fw(4) - configured as bootup firmware by indicated firmware(ID)."
--        ::= { swMultiImageCtrlEntry 4 }    
                       
    -- ***********************
    -- agentIpProtocolConfig *
    -- ***********************
    agentIpProtoConfig      OBJECT IDENTIFIER ::= { agentGeneralMgmt 3 }

    agentIpNumOfIf OBJECT-TYPE
        SYNTAX  Integer32
        MAX-ACCESS  read-only
        STATUS  current
        DESCRIPTION
            "The total number of IP interfaces supported by this agent."
        ::= {  agentIpProtoConfig 1 }

    agentIpTftpServerAddr OBJECT-TYPE
        SYNTAX  IpAddress
        MAX-ACCESS  read-write
        STATUS  obsolete
        DESCRIPTION
            "The IP Address of TFTP Server."
        ::= {  agentIpProtoConfig 2 }
	
    agentIpGetIpFrom OBJECT-TYPE
        SYNTAX  INTEGER {
                    other(1),
                    disabled(2),
                    bootp(3),
                    dhcp(4)
                }
        MAX-ACCESS  read-write
        STATUS  current
        DESCRIPTION
            "This object indicates whether the agent get its system IP address
             from Bootp/DHCP server at start up."
        ::= { agentIpProtoConfig 3 }	

    agentIpAutoconfig OBJECT-TYPE
        SYNTAX  INTEGER {
                    enabled(1),
                    disabled(2)
                }
        MAX-ACCESS  read-write
        STATUS  current
        DESCRIPTION
            ""
        ::= { agentIpProtoConfig 4 }
        
	-- End of agentIpIfTable ---------  
	
-- ******************************************************************************************	
-- Add common trap management 
-- ******************************************************************************************
      
	agentNotify	OBJECT IDENTIFIER ::= { agentGeneralMgmt 4 }  
	  
	agentNotifMgmt      OBJECT IDENTIFIER ::= { agentNotify 1 }  

-- ******************************************************************************************	
--	agentNotifMgmt
-- ******************************************************************************************
   
    systemTrapsSeverity OBJECT-TYPE
        SYNTAX  AgentNotifyLevel 
        MAX-ACCESS  read-write
        STATUS  current
        DESCRIPTION
            "Indicate the level of  system severity control,The system has a severity level control 
            and each trap should be along with a severity control. When trap event occurs 
            and its severity is higher than the system severity control level, the trap works 
            as it defined. If the event severity is lower than the system severity control level,
            the event is ignored as if it did not occur."
        ::= { agentNotifMgmt 1 }     
        		    
    systemLogsSeverity OBJECT-TYPE
        SYNTAX  AgentNotifyLevel 
        MAX-ACCESS  read-write
        STATUS  current
        DESCRIPTION
            "Indicate the level of  system severity control,The system has a severity level control 
            and each log should be along with a severity control. When log event occurs 
            and its severity is higher than the system severity control level, the log works 
            as it defined. If the event severity is lower than the system severity control level,
            the event is ignored as if it did not occur."
        ::= { agentNotifMgmt 2 }  
               		      
    -- ************************
    -- agentIptrapMangerTable *
    -- ************************

--	agentIpTrapManager	OBJECT IDENTIFIER ::= { agentGeneralMgmt 4 }
	
--    agentIpTrapManagerTable OBJECT-TYPE-
--        SYNTAX  SEQUENCE OF AgentIpTrapManagerEntry
--        MAX-ACCESS  not-accessible
--        STATUS  current
--        DESCRIPTION
--            "A list of trap managers to which SNMP traps will be sent."
--        ::= {  agentIpTrapManager 1 }

--    agentIpTrapManagerEntry OBJECT-TYPE
--        SYNTAX  AgentIpTrapManagerEntry
--        MAX-ACCESS  not-accessible
--        STATUS  obsolete
--        DESCRIPTION
--            "Each entry contains the particular trap manager settings."
--        INDEX   { agentIpTrapManagerIpAddr }
--        ::= { agentIpTrapManagerTable 1 }

-- *****************************************************************************
--
-- *****************************************************************************
        
--    agentTrapManagerTable OBJECT-TYPE
--        SYNTAX  SEQUENCE OF AgentTrapManagerEntry
--        MAX-ACCESS  not-accessible
--        STATUS  current
--        DESCRIPTION
--            "A list of trap managers to which SNMP traps will be sent."
--        ::= {  agentIpTrapManager 2 }

--    agentTrapManagerEntry OBJECT-TYPE
--        SYNTAX  AgentTrapManagerEntry
--        MAX-ACCESS  not-accessible
--        STATUS  current
--        DESCRIPTION
--            "Each entry contains the particular trap manager settings."
--        INDEX   { agentTrapManagerIndex }
--        ::= { agentTrapManagerTable 1 }

--    AgentTrapManagerEntry ::= 
--        SEQUENCE {
--				    agentTrapManagerIndex
--				        INTEGER,
--                    agentTrapManagerIpAddr
--                        IpAddress,
--                    agentTrapManagerComm
--                        DisplayString,
--                    agentTrapManagerMsgVer
--                        INTEGER,
--                    agentTrapManagerStatus
--                        INTEGER
--        }

--	agentTrapManagerIndex  OBJECT-TYPE
--	    SYNTAX     INTEGER (1..65535)
--	    MAX-ACCESS not-accessible
--	    STATUS     current
--	    DESCRIPTION
--	        "A value that uniquely identifies this trapDestEntry."
--	    ::= { agentTrapManagerEntry 1 }
    
--    agentTrapManagerIpAddr OBJECT-TYPE
--        SYNTAX  IpAddress
--        MAX-ACCESS  read-write
--        STATUS  current
--        DESCRIPTION
--            "The IP address where SNMP traps will be destined for"
--        ::= { agentTrapManagerEntry 2 }

--    agentTrapManagerComm OBJECT-TYPE
--        SYNTAX  DisplayString (SIZE (0..20))
--        MAX-ACCESS  read-write
--        STATUS  current
--        DESCRIPTION
--            "The community string used to encode SNMP trap packet to be sent to the trap
--             manager."
--        ::= { agentTrapManagerEntry 3 }
        
--    agentTrapManagerMsgVer OBJECT-TYPE
--        SYNTAX  INTEGER {
--                    snmpAgentVersionDependent(1),
--                    v1Trap(2),
--                    v2Trap(3)
--                }
--        MAX-ACCESS  read-write
--        STATUS  current
--        DESCRIPTION
--            "This object indicates the version of trap packets to be sent to
--             this trap manager. the default setting is SNMPAgentVersionDependent .
             
--			 Note:
--			 Because these funiction will be limited by the system support. Some of the 
--			 select item will invalid. When one of the item user select,it will response with 
--			 bad-value status.	             "
--        ::= { agentTrapManagerEntry 4 }               

--    agentTrapManagerStatus OBJECT-TYPE
--        SYNTAX  INTEGER {
--                    other(1),
--                    disabled(2),
--                    enabled(3)
--                }
--        MAX-ACCESS  read-write
--        STATUS  current
--        DESCRIPTION
--            "This object indicates whether or not the trap should be sent to
--             this trap manager."
--        ::= { agentTrapManagerEntry 5 }	          
        

--
-- Add for Slip_Console mode swtich 11-9-2001 WindChen
--
--	agentConsoleModeManager	OBJECT IDENTIFIER ::= { agentGeneralMgmt 5 }
	

        
--
-- Slip Mode Manager
--	
--	agentSlipModeManager	OBJECT IDENTIFIER ::= { agentGeneralMgmt 6 }


        

-- ******************************************************************************************	
-- Add common trap management 
-- ******************************************************************************************	
     
        
--	agentNotify	OBJECT IDENTIFIER ::= { agentGeneralMgmt 7 }  
	  
	  
	  
--	agentNotifMgmt      OBJECT IDENTIFIER ::= { agentNotify 1 }  
--	agentNotifFirmware   OBJECT IDENTIFIER ::= { agentNotify 2 }  
	
	
	
--	agentNotifyPrefix OBJECT IDENTIFIER ::= { agentNotifFirmware 0 }  

	

	
-- ******************************************************************************************	
--	agentNotifMgmt
-- ******************************************************************************************

--    systemTrapsSeverity OBJECT-TYPE
--        SYNTAX  AgentNotifyLevel 
--        MAX-ACCESS  read-write
--        STATUS  current
--        DESCRIPTION
--            "Indicate the level of  all system trap.
--			"
--        ::= { agentNotifMgmt 1 }

--	notifFirmwareMgmt OBJECT IDENTIFIER ::= { agentNotifMgmt 2 }  
     
-- ******************************************************************************************	

--    systemRestartTrapSeverity OBJECT-TYPE
--        SYNTAX  AgentNotifyLevel 
--        MAX-ACCESS  read-write
--        STATUS  current
--        DESCRIPTION
--            "Indicate the level of  system Restart detection.
--			"

--        ::= { notifFirmwareMgmt 1 }	
        
--    saveToNVRAMTrapSeverity OBJECT-TYPE
--        SYNTAX  AgentNotifyLevel 
--        MAX-ACCESS  read-write
--        STATUS  current
--        DESCRIPTION
--            "Indicate the level of  SaveToNV-RAM detection.
--			"

--        ::= { notifFirmwareMgmt 2 }	

--    fileTransferStatusChangeTrapSeverity OBJECT-TYPE
--        SYNTAX  AgentNotifyLevel 
--        MAX-ACCESS  read-write
--        STATUS  current
--        DESCRIPTION
--            "Indicate the level of  FileTransferStatusChange detection.
--			"

--        ::= { notifFirmwareMgmt 3 }	         


--    setToFactoryDefaultTrapSeverity OBJECT-TYPE
--        SYNTAX  AgentNotifyLevel 
--        MAX-ACCESS  read-write
--        STATUS  current
--        DESCRIPTION
--            "Indicate the level of  SetToFactoryDefault detection.
--			"

--        ::= { notifFirmwareMgmt 4 }	           
        
   	

-- ******************************************************************************************        

-- agentNotifFirmware OBJECT IDENTIFIER ::= { agentNotifyPrefix 0 }

-- ******************************************************************************************	
--	agentNotifFirmware
-- ******************************************************************************************
	
--    agentsystemRestart NOTIFICATION-TYPE
--        OBJECTS {
--              trapInfosystemRestart
--        		}
--        STATUS  current        		
--        DESCRIPTION
--            " This trap contain the reboot informaton. "

--		::= { agentNotifyPrefix 1 }          
        
		
--    agentSaveToNVRAM NOTIFICATION-TYPE
--        OBJECTS         { unitID
--                        }        
--        STATUS  current
--        DESCRIPTION
--            "The trap is sent whenever save all configuration of device to NV-RAM has been processed . "
             
--        ::= { agentNotifyPrefix 2 }    
        
--    agentFileTransferStatusChange NOTIFICATION-TYPE
--        OBJECTS         { 
--        					unitID,
--                          agentStatusFileTransfer
--                        }
--        STATUS          current
--        DESCRIPTION     "File transfer status change notification."
--        ::= { agentNotifyPrefix 3 }	
        
--    agentSetToFactoryDefault NOTIFICATION-TYPE
--        OBJECTS         { unitID
--                        }        
--        STATUS  current
--        DESCRIPTION
--            "The trap is sent whenever  the Set to factory default setting has been processed . "
             
--        ::= { agentNotifyPrefix 4 }           
        

-- ******************************************************************************************	
--	agentNotifEquipment
-- ******************************************************************************************        
   
      
-- ******************************************************************************************	
--	notificationBidings
-- ******************************************************************************************        		 
	 
--    notificationBidings OBJECT IDENTIFIER ::= { agentNotifFirmware 1 }
                
--    unitID OBJECT-TYPE
--        SYNTAX     INTEGER
--        MAX-ACCESS accessible-for-notify
--        STATUS     current
--        DESCRIPTION
--            "The Unit ID of the device which trigger the event"
--        ::= { notificationBidings 1 }                          
        
           	        
--    trapInfosystemRestart   OBJECT-TYPE
--        SYNTAX  DisplayString (SIZE (0..64))
--        MAX-ACCESS  read-only
--        STATUS  current
--        DESCRIPTION
--            "This object indicates the last time reboot information.
--            "
--        ::= { notificationBidings 2 }         
	 
	           
END
